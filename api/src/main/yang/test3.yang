module test3 {
    yang-version 1;
    namespace "urn:opendaylight:params:xml:ns:yang:test3";
    prefix "test3";

    revision "2015-01-05" {
        description "Initial revision of test3 model";
    }
    
    typedef d-id-type {
        type string {
            length "10..10";
            pattern "dev-[A-Za-z]{1,4}[\d]*";
        }
    }   
    
    typedef d-type-type {
        type enumeration {
            enum ROUTER {
                value "0";
            }
            enum SWITCH {
                value "1";
            }
        }
    }
    
    grouping device-grouping {
        leaf "d-id" { type string; }
        leaf "d-type" {type d-type-type; }
        leaf "ip-address" {type string;}
        leaf "d-name" {type string; mandatory true;}
        leaf "img-id" {type string;}
    }
    
    grouping img-grouping {
        leaf id { type string;}
        leaf path { type string;}
    }
    
    container imgs {
        list img {
           key "id";
           uses img-grouping;
        }
    }
    
    container devices {        
        list device {
            key "d-id";
            uses device-grouping;            
        }
    }
    
    rpc get-device-info {
       input {
          leaf  d-id { type d-id-type;}
       }
       output {
          uses device-grouping;
       }
    }
    
    rpc add-device {
       input {
          uses device-grouping;
       }
       output {
          leaf result {type string;}
       }
    }
    container list-test {
        list a-list {
            key "a-id";
            leaf a-id {type string;}
            list b-list {
                key "value";
                leaf value {type string;}
            }
        }
    }
    
    container test-exec {
        config true;

        list outer-list {
            key id;
            leaf id {
                type int32;
            }

           list inner-list {
                key name;
                leaf name {
                    type int32;
                }
                leaf value {
                    type string;
                }
            }
        }
    }
            
}
